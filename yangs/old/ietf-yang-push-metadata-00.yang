module ietf-yang-push-metadata {
  yang-version 1.1;
  namespace
    "urn:ietf:params:xml:ns:yang:ietf-yang-push-metadata";
  prefix ypm;
  import ietf-yang-types {
    prefix yang;
    reference
      "RFC 6991: Common YANG Data Types";
  }
  import ietf-subscribed-notifications {
    prefix sn;
    reference
      "RFC 8639: Subscription to YANG Notifications";
  }
  import ietf-yang-push {
    prefix yp;
    reference
      "RFC 8641: Subscription to YANG Notifications for Datastore Updates";
  }
  import ietf-yang-revisions {
    prefix rev;
    reference
      "RFC XXXX: draft-ietf-netmod-yang-module-versioning-06, Updated YANG
      Module Revision Handling";
  }
  import ietf-yang-semver {
    prefix ysver;
    reference
      "RFC XXXX: draft-ietf-netmod-yang-semver-07, YANG Semantic Versioning";
  }

  organization "IETF NETCONF (Network Configuration) Working Group";
  contact
    "WG Web:   <http:/tools.ietf.org/wg/netconf/>
     WG List:  <mailto:netconf@ietf.org>

     Authors:  Thomas Graf
               <mailto:thomas.graf@swisscom.com>
               Benoit Claise
               <mailto:benoit.claise@huawei.com>
               Alex Huang Feng
               <mailto:alex.huang-feng@insa-lyon.fr>";

  description
    "Defines YANG push event notification header with metadata.

    Copyright (c) 2022 IETF Trust and the persons identified as
    authors of the code.  All rights reserved.

    Redistribution and use in source and binary forms, with or without
    modification, is permitted pursuant to, and subject to the license
    terms contained in, the Revised BSD License set forth in Section
    4.c of the IETF Trust's Legal Provisions Relating to IETF Documents
    (https://trustee.ietf.org/license-info).

    This version of this YANG module is part of RFC XXXX; see the RFC
    itself for full legal notices.";

  revision 2022-09-21 {
    description
      "First revision";
    reference
      "RFC XXXX: Support of Versioning in YANG Notifications Subscription";
  }

  feature yang-push-metadata-supported {
    description
      "This feature indicates the YANG Notifications have the metadata 
      defined in this YANG module.";
  }

  grouping yang-push-module-version {
    leaf revision {
      type rev:revision-date-or-label;
      description
        "This references the YANG module revision of the sent notification.";
    }
    leaf revision-label {
      type ysver:version;
      description
        "This references the YANG module semversion of the sent notification.";
    }
  }

  grouping yang-push-metadata {
    leaf module {
      type string;
      description
        "This references the YANG module of the sent notification.";
    }
    leaf namespace {
      type string;
      description
        "This references the YANG module namespace of the sent notification.";
    }

    uses ypm:yang-push-module-version;

    leaf datastore-xpath-filter {
      type yang:xpath1.0;
      if-feature "sn:xpath";
      description
        "This references the YANG module xpath of the sent notification.";
    }
    anydata datastore-subtree-filter {
      if-feature "sn:subtree";
      description
        "This references the YANG module subtree of the sent notification.";
    }
  }
  // Event notifications
  augment "/yp:push-update" {
    description
      "This augmentation adds the module, the namespace, the revision, the 
      semversion, the xpath and the subtree in the push-update notification";
    uses ypm:yang-push-metadata;
  }

  augment "/yp:push-change-update" {
    description
      "This augmentation adds the module, the namespace, the revision, the 
      semversion, the xpath and the subtree in the push-change-update notification";
      uses ypm:yang-push-metadata;
  }

  // Subscription parameters
  augment "/sn:establish-subscription/sn:input/sn:target" {
    uses ypm:yang-push-module-version;
  }
  augment "/sn:modify-subscription/sn:input/sn:target" {
    uses ypm:yang-push-module-version;
  }

  // Subscription notifications
  augment "/sn:subscription-started/sn:target" {
    uses ypm:yang-push-module-version;
  }
  augment "/sn:subscription-modified/sn:target" {
    uses ypm:yang-push-module-version;
  }

  // Subscription container
  augment "/sn:subscriptions/sn:subscription/sn:target" {
    uses ypm:yang-push-module-version;
  }
}
